NAGIOS-ROOT-MIB DEFINITIONS ::= BEGIN
IMPORTS
  MODULE-IDENTITY, enterprises
    FROM SNMPv2-SMI
  TEXTUAL-CONVENTION
    FROM SNMPv2-TC;


nagios MODULE-IDENTITY
    LAST-UPDATED "200503090000Z" -- March 9, 2005
    ORGANIZATION "Nagios"
    CONTACT-INFO
      " Subhendu Ghosh

      Telephone: +1 201 232 2851
      Email: sghosh@users.sourceforge.net

      Nagios Information:
        http://www.nagios.org
      "
    DESCRIPTION
      "Objects for Nagios(tm) NMS"
    REVISION "200503090000Z" -- March 9, 2005
    DESCRIPTION
      "Spell check"
REVISION "200501200000Z" --January 20, 2005
    DESCRIPTION
      "Initial Version"
    ::= {enterprises 20006}

--
-- Textual Conventions
--

NotifyType ::= TEXTUAL-CONVENTION
  STATUS current
  DESCRIPTION
    "A string identifying the type of notification that is being sent
    (PROBLEM, RECOVERY, ACKNOWLEDGEMENT, FLAPPINGSTART or FLAPPINGSTOP).
    "
  SYNTAX INTEGER {
    problem(0),
    recovery(1),
    acknowledgement(2),
    flappingstart(3),
    flappingstop(4)
    }

HostStateID ::= TEXTUAL-CONVENTION
  STATUS current
  DESCRIPTION
    "A number that corresponds to the current state of the host: 0=UP, 1=DOWN,
    2=UNREACHABLE."
  SYNTAX INTEGER {
    up(0),
    down(1),
    unreachable(3)
    }

HostStateType ::= TEXTUAL-CONVENTION
  STATUS current
  DESCRIPTION
    "A string indicating the state type for the current host check (HARD or
    SOFT). Soft states occur when host checks return a non-OK (non-UP) state
    and are in the process of being retried. Hard states result when host
    checks have been checked a specified maximum number of times."
  SYNTAX INTEGER {
    hard(0),
    soft(1)
    }

ServiceStateID ::= TEXTUAL-CONVENTION
  STATUS current
  DESCRIPTION
    "A number that corresponds to the current state of the service: 0=OK,
    1=WARNING, 2=CRITICAL, 3=UNKNOWN.
    "
  SYNTAX INTEGER{
    ok(0),
    warning(1),
    critical(2),
    unknown(3)
    }


END
